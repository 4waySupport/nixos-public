-- $Id: Synergy_100G_hpeUserInitiatedTrap.mib,v 1.0 $

-- Proprietary MIB follows


syn100GhpeTestTrap DEFINITIONS ::= BEGIN

IMPORTS
   MODULE-IDENTITY, OBJECT-TYPE, NOTIFICATION-TYPE, enterprises  FROM SNMPv2-SMI
   TruthValue, DisplayString                              FROM SNMPv2-TC
--   IpAddressIfIndex                                       FROM IP-MIB
   InetAddress, InetAddressType          FROM INET-ADDRESS-MIB
   MODULE-COMPLIANCE, OBJECT-GROUP       FROM SNMPv2-CONF
   SnmpAdminString, SnmpEngineID,
   snmpAuthProtocols, snmpPrivProtocols  FROM SNMP-FRAMEWORK-MIB;

syn100GhpeTestTrap  MODULE-IDENTITY
      LAST-UPDATED "201707250000Z"
      ORGANIZATION "Hewlett Packard Enterprise"
      CONTACT-INFO "Hewlett Packard Enterprise Support Center
                   www.hpe.com/support<http://www.hpe.com/support>
                   US, Canada & Caribbean: 1-800-633-3600
                   UK & Ireland: 0845 161 0050
                   Asia Pacific Region: 61-3-8877-5000"
      DESCRIPTION
          "CUSTOM MIB"
      REVISION "201707250000Z"
      DESCRIPTION
          "CUSTOM MIB"

         ::= { enterprises 11.5.7.5.9.1.4030 }

-- ------------------------------------------------------------
--         groups in the MIB
-- ------------------------------------------------------------

    hpCustTraps   OBJECT IDENTIFIER ::=    {syn100GhpeTestTrap 5}


-- ------------------------------------------------------------------
--       User Generated Trap
-- ------------------------------------------------------------------

syn100GUserInitiatedTrap NOTIFICATION-TYPE
--    OBJECTS {
--        IpAddressIfIndex
--    }

    STATUS  current
    DESCRIPTION
              "Test trap sent from HPE VC SE 100Gb F32 Interconnect Module."
    ::= { hpCustTraps  1}
END
